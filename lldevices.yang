module lldevices {
    namespace "http://tail-f.com/ns/example/lldevices";
    prefix lldevices;


    grouping llmanufdata {
        leaf ProductID {
            type string;
        }
        leaf SERIAL {
            type bool;
        }
        leaf MAC {
            type string;
        }
    }

    grouping llcards {
        leaf slot-id {
            type int16;
        }
        leaf card-type {
            type string;
        }
    }
    
    grouping interface {
        leaf fullspeed {
            type int64;
        }
    }

    container lldevices {
        list lldevice {
            key device-id;
            leaf device-id {
                type string;
            }
            uses llmanufdata;
            uses llcards;
            uses interface;
        }
    }
    
}
